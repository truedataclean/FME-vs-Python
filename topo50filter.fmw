FME workspace topo50filter.fmw

Parameters:
- SourceDataset_SHAPEFILE_6 = N:\temp\DPark\Karl\lds-nz-150k-tile-index-SHP\nz-150k-tile-index.shp   # Source Esri Shapefile(s)
- DestDataset_SHAPEFILE = C:\Temp\Topo\TopoBDE00-filtered   # Destination Esri Shapefile Folder

Readers:
- SHAPEFILE_2: SHAPEFILE from $(SourceDataset_SHAPEFILE_6)

Writers:
- SHAPEFILE_1: SHAPEFILE to $(DestDataset_SHAPEFILE)

Note: nz-150k-tile-index: nz-150k-tile-index [SHAPEFILE]
nz-150k-tile-index (reader SHAPEFILE_2)
    attributes: sheet_code varchar(4), topo50_cov varchar(20)
    -> BoundingBoxReplacer
Creator
    GEOMTYPE = Geometry Object
    NUM = 1
    CREATED -> FeatureReader [INITIATOR]
Note: Input : Pre-reblocker Folder
FeatureReader
    ATTRIBUTES = airport_poly,"t50_fid,name_ascii,macronated,name",boatramp_cl,"t50_fid,name_ascii,macronated,name",boom_cl,t50_fid,breakwater_cl,t50_fid,bridge_cl,"t50_fid,constr_typ,status,use_1,use_2,name_ascii,macronated,name",building_poly,"t50_fid,status,bldg_use,name_ascii,macronated,name",cableway_industrial_cl,"t50_fid,mtlconveyd",cableway_people_cl,"t50_fid,restrictns",canal_cl,"gazfeatid,t50_fid,name_ascii,macronated,name",canal_poly,"gazfeatid,t50_fid,name_ascii,macronated,name",cemetery_poly,"t50_fid,name_ascii,macronated,name",cliff_edge,t50_fid,coastline,"t50_fid,elevation",cutting_edge,t50_fid,dam_cl,"t50_fid,dam_status,name_ascii,macronated,name",drain_cl,"gazfeatid,t50_fid,name_ascii,macronated,name",dredge_tailing_cl,t50_fid,dry_dock_poly,"t50_fid,type",embankment_cl,"t50_fid,embkmt_use,name_ascii,macronated,name",exotic_poly,"t50_fid,species",fastice_poly,t50_fid,fence_cl,t50_fid,ferry_crossing_cl,t50_fid,fish_farm_poly,"t50_fid,type,species",flume_cl,t50_fid,golf_course_poly,"t50_fid,name_ascii,macronated,name",gravel_pit_poly,t50_fid,ice_poly,t50_fid,island_poly,"t50_fid,grp_ascii,grp_name,name_ascii,macronated,name,grp_macron",ladder_cl,"t50_fid,materials",lagoon_poly,"t50_fid,elevation,name_ascii,macronated,name",lake_poly,"t50_fid,elevation,grp_ascii,grp_name,perennial,temperatur,lake_use,name_ascii,macronated,name,grp_macron",landfill_poly,"t50_fid,name_ascii,macronated,name",linz_map_sheet,"t50_fid,sheet_code,sheet_name,edition,revised",mangrove_poly,t50_fid,marine_farm_cl,"t50_fid,species",marine_farm_poly,"t50_fid,species",mine_poly,"t50_fid,status,substance,visibility,name_ascii,macronated,name",monument_pnt,"t50_fid,name_ascii,macronated,name",moraine_poly,t50_fid,moraine_wall_poly,t50_fid,mud_poly,t50_fid,native_poly,t50_fid,orchard_poly,t50_fid,pa_pnt,"t50_fid,name_ascii,macronated,name",pipeline_cl,"t50_fid,pipe_use,visibility",pond_poly,"t50_fid,name_ascii,macronated,name,pond_use",powerline_cl,"t50_fid,support_ty",pumice_pit_poly,t50_fid,quarry_poly,"t50_fid,name_ascii,macronated,name,status,substance",racetrack_cl,"t50_fid,name_ascii,macronated,name,track_type,track_use",racetrack_poly,"t50_fid,name_ascii,macronated,name,track_type,track_use",railway_cl,"t50_fid,name_ascii,macronated,name,status,track_type,rway_use,veh_type",rapid_cl,"t50_fid,name_ascii,macronated,name",rapid_poly,"t50_fid,name_ascii,macronated,name",reef_poly,"t50_fid,name_ascii,macronated,name,compositn",reservoir_poly,"t50_fid,lid_type",residential_area_poly,"t50_fid,name_ascii,macronated,name",rifle_range_poly,t50_fid,river_cl,"gazfeatid,t50_fid,name_ascii,macronated,name",river_poly,"gazfeatid,t50_fid,name_ascii,macronated,name",road_cl,"t50_fid,name_ascii,macronated,name,hway_num,rna_sufi,lane_count,way_count,status,surface",rock_poly,"t50_fid,name_ascii,macronated,name",runway_poly,"t50_fid,status,surface,runway_use",sand_poly,t50_fid,scattered_scrub_poly,t50_fid,scree_poly,t50_fid,scrub_poly,t50_fid,shelter_belt_cl,t50_fid,shingle_poly,t50_fid,shoal_poly,"t50_fid,name_ascii,macronated,name",showground_poly,t50_fid,siphon_poly,"t50_fid,status",ski_lift_cl,t50_fid,ski_tow_cl,t50_fid,slip_edge,t50_fid,slipway_cl,"t50_fid,name_ascii,macronated,name",snow_poly,t50_fid,spillway_edge,t50_fid,sportsfield_poly,"t50_fid,name_ascii,macronated,name",swamp_poly,"t50_fid,name_ascii,macronated,name",tank_poly,"t50_fid,store_item,tank_type",telephone_cl,t50_fid,track_cl,"t50_fid,name_ascii,macronated,name,status,track_type,track_use",tunnel_cl,"t50_fid,name_ascii,macronated,name,status,type,use1,use2",vineyard_poly,t50_fid,walkwire_cl,t50_fid,water_race_cl,"t50_fid,name_ascii,macronated,name,status",waterfall_cl,"t50_fid,name_ascii,macronated,name,height",waterfall_edge,"t50_fid,name_ascii,macronated,name,height",waterfall_poly,"t50_fid,name_ascii,macronated,name,height",weir_cl,t50_fid,wharf_cl,"t50_fid,name_ascii,macronated,name,status,wharf_use",wharf_edge,t50_fid
    ATTR_ACCUM_MODE = Only Use Result
    COMBINE_GEOM = Use Result
    DATASET = C:\Temp\Topo\TopoBDE00-pre-reblocker\*.shp
    FORMAT = SHAPEFILE
    GEOMETRY_TYPES = airport_poly,""",fme_area""",boatramp_cl,""",fme_line""",boom_cl,""",fme_line""",breakwater_cl,""",fme_line""",bridge_cl,""",fme_line""",building_poly,""",fme_area""",cableway_industrial_cl,""",fme_line""",cableway_people_cl,""",fme_line""",canal_cl,""",fme_line""",canal_poly,""",fme_area""",cemetery_poly,""",fme_area""",cliff_edge,""",fme_line""",coastline,""",fme_line""",cutting_edge,""",fme_line""",dam_cl,""",fme_line""",drain_cl,""",fme_line""",dredge_tailing_cl,""",fme_line""",dry_dock_poly,""",fme_area""",embankment_cl,""",fme_line""",exotic_poly,""",fme_area""",fastice_poly,""",fme_area""",fence_cl,""",fme_line""",ferry_crossing_cl,""",fme_line""",fish_farm_poly,""",fme_area""",flume_cl,""",fme_line""",golf_course_poly,""",fme_area""",gravel_pit_poly,""",fme_area""",ice_poly,""",fme_area""",island_poly,""",fme_area""",ladder_cl,""",fme_line""",lagoon_poly,""",fme_area""",lake_poly,""",fme_area""",landfill_poly,""",fme_area""",linz_map_sheet,""",fme_area""",mangrove_poly,""",fme_area""",marine_farm_cl,""",fme_line""",marine_farm_poly,""",fme_area""",mine_poly,""",fme_area""",monument_pnt,""",fme_point""",moraine_poly,""",fme_area""",moraine_wall_poly,""",fme_area""",mud_poly,""",fme_area""",native_poly,""",fme_area""",orchard_poly,""",fme_area""",pa_pnt,""",fme_point""",pipeline_cl,""",fme_line""",pond_poly,""",fme_area""",powerline_cl,""",fme_line""",pumice_pit_poly,""",fme_area""",quarry_poly,""",fme_area""",racetrack_cl,""",fme_line""",racetrack_poly,""",fme_area""",railway_cl,""",fme_line""",rapid_cl,""",fme_line""",rapid_poly,""",fme_area""",reef_poly,""",fme_area""",reservoir_poly,""",fme_area""",residential_area_poly,""",fme_area""",rifle_range_poly,""",fme_area""",river_cl,""",fme_line""",river_poly,""",fme_area""",road_cl,""",fme_line""",rock_poly,""",fme_area""",runway_poly,""",fme_area""",sand_poly,""",fme_area""",scattered_scrub_poly,""",fme_area""",scree_poly,""",fme_area""",scrub_poly,""",fme_area""",shelter_belt_cl,""",fme_line""",shingle_poly,""",fme_area""",shoal_poly,""",fme_area""",showground_poly,""",fme_area""",siphon_poly,""",fme_area""",ski_lift_cl,""",fme_line""",ski_tow_cl,""",fme_line""",slip_edge,""",fme_line""",slipway_cl,""",fme_line""",snow_poly,""",fme_area""",spillway_edge,""",fme_line""",sportsfield_poly,""",fme_area""",swamp_poly,""",fme_area""",tank_poly,""",fme_area""",telephone_cl,""",fme_line""",track_cl,""",fme_line""",tunnel_cl,""",fme_line""",vineyard_poly,""",fme_area""",walkwire_cl,""",fme_line""",water_race_cl,""",fme_line""",waterfall_cl,""",fme_line""",waterfall_edge,""",fme_line""",waterfall_poly,""",fme_area""",weir_cl,""",fme_line""",wharf_cl,""",fme_line""",wharf_edge,""",fme_line"""
    INTERACT = NONE
    ORDER_RESULTS = No
    OUTPUT_ADD_SCHEMA_ATTRIBUTES = NO
    OUTPUT_FEATURES_DISPLAY = Schema and Data Features
    SHAPEFILE_ALLOW_MISMATCHED_SHZ_BASENAME = No
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    airport_poly -> SpatialFilter [Candidate]
    boatramp_cl -> SpatialFilter [Candidate]
    boom_cl -> SpatialFilter [Candidate]
    breakwater_cl -> SpatialFilter [Candidate]
    bridge_cl -> SpatialFilter [Candidate]
    building_poly -> SpatialFilter [Candidate]
    cableway_industrial_cl -> SpatialFilter [Candidate]
    cableway_people_cl -> SpatialFilter [Candidate]
    canal_cl -> SpatialFilter [Candidate]
    canal_poly -> SpatialFilter [Candidate]
    cemetery_poly -> SpatialFilter [Candidate]
    cliff_edge -> SpatialFilter [Candidate]
    coastline -> SpatialFilter [Candidate]
    cutting_edge -> SpatialFilter [Candidate]
    dam_cl -> SpatialFilter [Candidate]
    drain_cl -> SpatialFilter [Candidate]
    dredge_tailing_cl -> SpatialFilter [Candidate]
    dry_dock_poly -> SpatialFilter [Candidate]
    embankment_cl -> SpatialFilter [Candidate]
    exotic_poly -> SpatialFilter [Candidate]
    fastice_poly -> SpatialFilter [Candidate]
    fence_cl -> SpatialFilter [Candidate]
    ferry_crossing_cl -> SpatialFilter [Candidate]
    fish_farm_poly -> SpatialFilter [Candidate]
    flume_cl -> SpatialFilter [Candidate]
    golf_course_poly -> SpatialFilter [Candidate]
    gravel_pit_poly -> SpatialFilter [Candidate]
    ice_poly -> SpatialFilter [Candidate]
    island_poly -> SpatialFilter [Candidate]
    ladder_cl -> SpatialFilter [Candidate]
    lagoon_poly -> SpatialFilter [Candidate]
    lake_poly -> SpatialFilter [Candidate]
    landfill_poly -> SpatialFilter [Candidate]
    linz_map_sheet -> SpatialFilter [Candidate]
    mangrove_poly -> SpatialFilter [Candidate]
    marine_farm_cl -> SpatialFilter [Candidate]
    marine_farm_poly -> SpatialFilter [Candidate]
    mine_poly -> SpatialFilter [Candidate]
    monument_pnt -> SpatialFilter [Candidate]
    moraine_poly -> SpatialFilter [Candidate]
    moraine_wall_poly -> SpatialFilter [Candidate]
    mud_poly -> SpatialFilter [Candidate]
    native_poly -> SpatialFilter [Candidate]
    orchard_poly -> SpatialFilter [Candidate]
    pa_pnt -> SpatialFilter [Candidate]
    pipeline_cl -> SpatialFilter [Candidate]
    pond_poly -> SpatialFilter [Candidate]
    powerline_cl -> SpatialFilter [Candidate]
    pumice_pit_poly -> SpatialFilter [Candidate]
    quarry_poly -> SpatialFilter [Candidate]
    racetrack_cl -> SpatialFilter [Candidate]
    racetrack_poly -> SpatialFilter [Candidate]
    railway_cl -> SpatialFilter [Candidate]
    rapid_cl -> SpatialFilter [Candidate]
    rapid_poly -> SpatialFilter [Candidate]
    reef_poly -> SpatialFilter [Candidate]
    reservoir_poly -> SpatialFilter [Candidate]
    residential_area_poly -> SpatialFilter [Candidate]
    rifle_range_poly -> SpatialFilter [Candidate]
    river_cl -> SpatialFilter [Candidate]
    river_poly -> SpatialFilter [Candidate]
    road_cl -> SpatialFilter [Candidate]
    rock_poly -> SpatialFilter [Candidate]
    runway_poly -> SpatialFilter [Candidate]
    sand_poly -> SpatialFilter [Candidate]
    scattered_scrub_poly -> SpatialFilter [Candidate]
    scree_poly -> SpatialFilter [Candidate]
    scrub_poly -> SpatialFilter [Candidate]
    shelter_belt_cl -> SpatialFilter [Candidate]
    shingle_poly -> SpatialFilter [Candidate]
    shoal_poly -> SpatialFilter [Candidate]
    showground_poly -> SpatialFilter [Candidate]
    siphon_poly -> SpatialFilter [Candidate]
    ski_lift_cl -> SpatialFilter [Candidate]
    ski_tow_cl -> SpatialFilter [Candidate]
    slip_edge -> SpatialFilter [Candidate]
    slipway_cl -> SpatialFilter [Candidate]
    snow_poly -> SpatialFilter [Candidate]
    spillway_edge -> SpatialFilter [Candidate]
    sportsfield_poly -> SpatialFilter [Candidate]
    swamp_poly -> SpatialFilter [Candidate]
    tank_poly -> SpatialFilter [Candidate]
    telephone_cl -> SpatialFilter [Candidate]
    track_cl -> SpatialFilter [Candidate]
    tunnel_cl -> SpatialFilter [Candidate]
    vineyard_poly -> SpatialFilter [Candidate]
    walkwire_cl -> SpatialFilter [Candidate]
    water_race_cl -> SpatialFilter [Candidate]
    waterfall_cl -> SpatialFilter [Candidate]
    waterfall_edge -> SpatialFilter [Candidate]
    waterfall_poly -> SpatialFilter [Candidate]
    weir_cl -> SpatialFilter [Candidate]
    wharf_cl -> SpatialFilter [Candidate]
    wharf_edge -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS TOUCHES
    USE_BOUNDING_BOX = No
    PASSED -> Shapefile1 (writer SHAPEFILE_1)
Note: Outs: TopoBDE00-filtered [SHAPEFILE]
Shapefile1 (writer SHAPEFILE_1)
    attributes: sheet_code varchar(4), topo50_cov varchar(20), Q__remnant varchar(3), t50_fid long, name_ascii varchar(75), macronated varchar(1), name varchar(75), constr_typ varchar(10), status varchar(8), use_1 varchar(12), use_2 varchar(12), bldg_use varchar(21), mtlconveyd varchar(4), restrictns varchar(6), gazfeatid long, elevation long, dam_status varchar(7), type varchar(8), embkmt_use varchar(10), species varchar(14), grp_ascii varchar(60), grp_name varchar(60), grp_macron varchar(1), materials varchar(5), perennial varchar(8), temperatur varchar(3), lake_use varchar(15), sheet_name varchar(50), edition varchar(30), revised varchar(60),
      substance varchar(10), visibility varchar(11), pipe_use varchar(8), pond_use varchar(16), support_ty varchar(5), track_type varchar(8), track_use varchar(7), rway_use varchar(6), veh_type varchar(9), compositn varchar(5), lid_type varchar(7), hway_num varchar(5), rna_sufi long, lane_count long, way_count varchar(7), surface varchar(10), runway_use varchar(9), store_item varchar(5), tank_type varchar(13), use1 varchar(12), use2 varchar(12), height long, wharf_use varchar(5), Q__predica varchar(254)

Bookmark: Index processing
BoundingBoxReplacer
    BBTYPE = MINBB
    BOXTYPE = 2D Oriented Bounding Box
    BOX -> Chopper
Chopper
    DEAGGREGATE_INPUT = Deaggregate
    MAX_VERTICES = 2
    MODE_LOOKUP = VERTEX
    REMNANT_ATTR = _remnant
    MODE = By Vertex
    CHOPPED -> Bufferer
Bufferer
    ANGLE = 22.5
    CAP_STYLE_LOOKUP = CAP_ARC
    CORNER_STYLE_LOOKUP = JOIN_ARC
    MODE = AREA
    OFFSET = 1
    OFFSET_UNITS = NONE
    PRECISION = APPROX
    CAP_STYLE = Arc
    CORNER_STYLE = Arc
    BUFFERED -> SpatialFilter [Filter]
