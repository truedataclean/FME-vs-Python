FME workspace river_name_reblocker_geopkg.fmw

Parameters:
- DestDataset_SHAPEFILE = N:\temp\DPark\Karl\ReverName\outs   # Destination Esri Shapefile Folder
- DestDataset_OGCGEOPACKAGE_3 = C:\Temp\Topo\river_name_out   # GeoPackage File
- DestDataset_OGCGEOPACKAGE = C:\Temp\Topo\river_name_out   # GeoPackage File

Writers:
- OGCGEOPACKAGE_1: OGCGEOPACKAGE to $(DestDataset_OGCGEOPACKAGE)
- OGCGEOPACKAGE_2: OGCGEOPACKAGE to $(DestDataset_OGCGEOPACKAGE_3)

River_Name: Creator
    GEOMTYPE = Geometry Object
    NUM = 1
    CREATED -> FeatureReader [INITIATOR]
AttributeManager_4
    ATTR_TABLE:
      REMOVE gazfeatid (int32)
      RENAME_SET_VALUE t50_fid > river_section_id (int32)
      RENAME_SET_VALUE fme_feature_type > feat_type (varchar(200))
    USER_EXPOSED_ATTRIBUTES = multi_reader_type,shapefile_type,multi_reader_full_id,multi_reader_id,$(FME_MF_NAME),$(DestDataset_SHAPEFILE),fme_feature_type
    -> river_line (writer OGCGEOPACKAGE_1)
AttributeManager_2
    ATTR_TABLE:
      REMOVE gazfeatid (int32)
      RENAME_SET_VALUE t50_fid > river_section_id (int32)
      RENAME_SET_VALUE fme_feature_type > feat_type (varchar(200))
    USER_EXPOSED_ATTRIBUTES = multi_reader_type,shapefile_type,multi_reader_full_id,multi_reader_id,$(FME_MF_NAME),$(DestDataset_SHAPEFILE),fme_feature_type
    -> river_polygons (writer OGCGEOPACKAGE_2)

Bookmark: Input
Note: Pre Reblocker directory
FeatureReader
    ATTRIBUTES = airport_poly,"t50_fid,name_ascii,macronated,name",boatramp_cl,"t50_fid,name_ascii,macronated,name",boom_cl,t50_fid,breakwater_cl,t50_fid,bridge_cl,"t50_fid,constr_typ,status,use_1,use_2,name_ascii,macronated,name",building_poly,"t50_fid,status,bldg_use,name_ascii,macronated,name",cableway_industrial_cl,"t50_fid,mtlconveyd",cableway_people_cl,"t50_fid,restrictns",canal_cl,"gazfeatid,t50_fid,name_ascii,macronated,name",canal_poly,"gazfeatid,t50_fid,name_ascii,macronated,name",cemetery_poly,"t50_fid,name_ascii,macronated,name",cliff_edge,t50_fid,coastline,"t50_fid,elevation",cutting_edge,t50_fid,dam_cl,"t50_fid,dam_status,name_ascii,macronated,name",drain_cl,"gazfeatid,t50_fid,name_ascii,macronated,name",dredge_tailing_cl,t50_fid,dry_dock_poly,"t50_fid,type",embankment_cl,"t50_fid,embkmt_use,name_ascii,macronated,name",exotic_poly,"t50_fid,species",fastice_poly,t50_fid,fence_cl,t50_fid,ferry_crossing_cl,t50_fid,fish_farm_poly,"t50_fid,type,species",flume_cl,t50_fid,golf_course_poly,"t50_fid,name_ascii,macronated,name",gravel_pit_poly,t50_fid,ice_poly,t50_fid,island_poly,"t50_fid,grp_ascii,grp_name,name_ascii,macronated,name,grp_macron",ladder_cl,"t50_fid,materials",lagoon_poly,"t50_fid,elevation,name_ascii,macronated,name",lake_poly,"t50_fid,elevation,grp_ascii,grp_name,perennial,temperatur,lake_use,name_ascii,macronated,name,grp_macron",landfill_poly,"t50_fid,name_ascii,macronated,name",linz_map_sheet,"t50_fid,sheet_code,sheet_name,edition,revised",mangrove_poly,t50_fid,marine_farm_cl,"t50_fid,species",marine_farm_poly,"t50_fid,species",mine_poly,"t50_fid,status,substance,visibility,name_ascii,macronated,name",monument_pnt,"t50_fid,name_ascii,macronated,name",moraine_poly,t50_fid,moraine_wall_poly,t50_fid,mud_poly,t50_fid,native_poly,t50_fid,orchard_poly,t50_fid,pa_pnt,"t50_fid,name_ascii,macronated,name",pipeline_cl,"t50_fid,pipe_use,visibility",pond_poly,"t50_fid,name_ascii,macronated,name,pond_use",powerline_cl,"t50_fid,support_ty",pumice_pit_poly,t50_fid,quarry_poly,"t50_fid,name_ascii,macronated,name,status,substance",racetrack_cl,"t50_fid,name_ascii,macronated,name,track_type,track_use",racetrack_poly,"t50_fid,name_ascii,macronated,name,track_type,track_use",railway_cl,"t50_fid,name_ascii,macronated,name,status,track_type,rway_use,veh_type",rapid_cl,"t50_fid,name_ascii,macronated,name",rapid_poly,"t50_fid,name_ascii,macronated,name",reef_poly,"t50_fid,name_ascii,macronated,name,compositn",reservoir_poly,"t50_fid,lid_type",residential_area_poly,"t50_fid,name_ascii,macronated,name",rifle_range_poly,t50_fid,river_cl,"gazfeatid,t50_fid,name_ascii,macronated,name",river_poly,"gazfeatid,t50_fid,name_ascii,macronated,name",road_cl,"t50_fid,name_ascii,macronated,name,hway_num,rna_sufi,lane_count,way_count,status,surface",rock_poly,"t50_fid,name_ascii,macronated,name",runway_poly,"t50_fid,status,surface,runway_use",sand_poly,t50_fid,scattered_scrub_poly,t50_fid,scree_poly,t50_fid,scrub_poly,t50_fid,shelter_belt_cl,t50_fid,shingle_poly,t50_fid,shoal_poly,"t50_fid,name_ascii,macronated,name",showground_poly,t50_fid,siphon_poly,"t50_fid,status",ski_lift_cl,t50_fid,ski_tow_cl,t50_fid,slip_edge,t50_fid,slipway_cl,"t50_fid,name_ascii,macronated,name",snow_poly,t50_fid,spillway_edge,t50_fid,sportsfield_poly,"t50_fid,name_ascii,macronated,name",swamp_poly,"t50_fid,name_ascii,macronated,name",tank_poly,"t50_fid,store_item,tank_type",telephone_cl,t50_fid,track_cl,"t50_fid,name_ascii,macronated,name,status,track_type,track_use",tunnel_cl,"t50_fid,name_ascii,macronated,name,status,type,use1,use2",vineyard_poly,t50_fid,walkwire_cl,t50_fid,water_race_cl,"t50_fid,name_ascii,macronated,name,status",waterfall_cl,"t50_fid,name_ascii,macronated,name,height",waterfall_edge,"t50_fid,name_ascii,macronated,name,height",waterfall_poly,"t50_fid,name_ascii,macronated,name,height",weir_cl,t50_fid,wharf_cl,"t50_fid,name_ascii,macronated,name,status,wharf_use",wharf_edge,t50_fid
    ATTR_ACCUM_MODE = Only Use Result
    COMBINE_GEOM = Use Result
    DATASET = C:\Temp\Topo\TopoBDE00-pre-reblocker\*.shp
    FEATURETYPES = canal_cl canal_poly drain_cl river_cl river_poly
    FORMAT = SHAPEFILE
    GEOMETRY_TYPES = airport_poly,""",fme_area""",boatramp_cl,""",fme_line""",boom_cl,""",fme_line""",breakwater_cl,""",fme_line""",bridge_cl,""",fme_line""",building_poly,""",fme_area""",cableway_industrial_cl,""",fme_line""",cableway_people_cl,""",fme_line""",canal_cl,""",fme_line""",canal_poly,""",fme_area""",cemetery_poly,""",fme_area""",cliff_edge,""",fme_line""",coastline,""",fme_line""",cutting_edge,""",fme_line""",dam_cl,""",fme_line""",drain_cl,""",fme_line""",dredge_tailing_cl,""",fme_line""",dry_dock_poly,""",fme_area""",embankment_cl,""",fme_line""",exotic_poly,""",fme_area""",fastice_poly,""",fme_area""",fence_cl,""",fme_line""",ferry_crossing_cl,""",fme_line""",fish_farm_poly,""",fme_area""",flume_cl,""",fme_line""",golf_course_poly,""",fme_area""",gravel_pit_poly,""",fme_area""",ice_poly,""",fme_area""",island_poly,""",fme_area""",ladder_cl,""",fme_line""",lagoon_poly,""",fme_area""",lake_poly,""",fme_area""",landfill_poly,""",fme_area""",linz_map_sheet,""",fme_area""",mangrove_poly,""",fme_area""",marine_farm_cl,""",fme_line""",marine_farm_poly,""",fme_area""",mine_poly,""",fme_area""",monument_pnt,""",fme_point""",moraine_poly,""",fme_area""",moraine_wall_poly,""",fme_area""",mud_poly,""",fme_area""",native_poly,""",fme_area""",orchard_poly,""",fme_area""",pa_pnt,""",fme_point""",pipeline_cl,""",fme_line""",pond_poly,""",fme_area""",powerline_cl,""",fme_line""",pumice_pit_poly,""",fme_area""",quarry_poly,""",fme_area""",racetrack_cl,""",fme_line""",racetrack_poly,""",fme_area""",railway_cl,""",fme_line""",rapid_cl,""",fme_line""",rapid_poly,""",fme_area""",reef_poly,""",fme_area""",reservoir_poly,""",fme_area""",residential_area_poly,""",fme_area""",rifle_range_poly,""",fme_area""",river_cl,""",fme_line""",river_poly,""",fme_area""",road_cl,""",fme_line""",rock_poly,""",fme_area""",runway_poly,""",fme_area""",sand_poly,""",fme_area""",scattered_scrub_poly,""",fme_area""",scree_poly,""",fme_area""",scrub_poly,""",fme_area""",shelter_belt_cl,""",fme_line""",shingle_poly,""",fme_area""",shoal_poly,""",fme_area""",showground_poly,""",fme_area""",siphon_poly,""",fme_area""",ski_lift_cl,""",fme_line""",ski_tow_cl,""",fme_line""",slip_edge,""",fme_line""",slipway_cl,""",fme_line""",snow_poly,""",fme_area""",spillway_edge,""",fme_line""",sportsfield_poly,""",fme_area""",swamp_poly,""",fme_area""",tank_poly,""",fme_area""",telephone_cl,""",fme_line""",track_cl,""",fme_line""",tunnel_cl,""",fme_line""",vineyard_poly,""",fme_area""",walkwire_cl,""",fme_line""",water_race_cl,""",fme_line""",waterfall_cl,""",fme_line""",waterfall_edge,""",fme_line""",waterfall_poly,""",fme_area""",weir_cl,""",fme_line""",wharf_cl,""",fme_line""",wharf_edge,""",fme_line"""
    INTERACT = NONE
    ORDER_RESULTS = No
    OUTPUT_ADD_SCHEMA_ATTRIBUTES = NO
    OUTPUT_FEATURES_DISPLAY = Schema and Data Features
    SELECTED_PORTS = canal_cl canal_poly drain_cl river_cl river_poly
    SHAPEFILE_ALLOW_MISMATCHED_SHZ_BASENAME = No
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    canal_cl -> AttributeManager_4
    canal_poly -> AttributeManager_2
    drain_cl -> AttributeManager_4
    river_cl -> AttributeManager_4
    river_poly -> AttributeManager_2

Bookmark: OUTs
river_line (writer OGCGEOPACKAGE_1)
    attributes: river_section_id mediumint, feat_type text(200), name_ascii text(75), macronated text(1), name text(75)
river_polygons (writer OGCGEOPACKAGE_2)
    attributes: river_section_id mediumint, feat_type text(200), name_ascii text(75), macronated text(1), name text(75)
